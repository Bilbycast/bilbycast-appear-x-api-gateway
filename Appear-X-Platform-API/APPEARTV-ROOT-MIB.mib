--  **************************************************************************
--  File Appear_Root.mib
--
--  Copyright (c) 2004-2021 by Appear AS
--
--  This document (SNMP mib file) is the intellectual property of
--  Appear AS and contains confidential information.
--  All reproduction and communication to third parties is strictly prohibited
--  without prior consent of Appear AS.
--
--  **************************************************************************

APPEARTV-ROOT-MIB DEFINITIONS ::= BEGIN

IMPORTS
    enterprises, MODULE-IDENTITY
        FROM SNMPv2-SMI;

appearTvRoot MODULE-IDENTITY

    LAST-UPDATED "202104121334Z" -- April 12, 2021

    ORGANIZATION "Appear AS"

    CONTACT-INFO "Appear AS
                  PO Box 8 Lilleaker
                  NO-0216 Oslo
                  Norway

                  mailto:support@appeartv.com
                  http://www.appeartv.com"

    DESCRIPTION
        "This MIB implements Appear root object identifiers"

    REVISION     "202104121334Z"
    DESCRIPTION
	"V01.01.03
         Moved appeartv and common after appearTvRoot. SMIv2 requires
         that MODULE-IDENTITY be the very first item defined in the module
         after the module header and IMPORTS section"

    REVISION     "200908311430Z"
    DESCRIPTION
	"V01.01.02
         Moved appeartv and common before appearTvRoot"

::= {appeartv 3}

appeartv OBJECT IDENTIFIER ::= {enterprises 23916}

common   OBJECT IDENTIFIER ::= {appeartv 1}

END
